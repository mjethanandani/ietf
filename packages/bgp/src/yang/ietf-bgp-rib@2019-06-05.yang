submodule ietf-bgp-rib {
  yang-version "1.1";
  belongs-to ietf-bgp {
    prefix "br";
  }

  /*
   * Import and Include
   */
  import ietf-bgp-types {
    prefix "bt";
    reference
      "RFC XXXX: BGP YANG Model for Service Provider Networks.";
  }

  import ietf-inet-types {
    prefix inet;
    reference
      "RFC 6991: Common YANG Types.";
  }

  import ietf-routing-types {
    prefix "rt";
    reference
      "RFC 8294: Routing Area YANG Types.";
  }
  

  include ietf-bgp-rib-types;
  include ietf-bgp-rib-tables;

  // groupings of attributes in three categories:
  //  - shared across multiple routes
  //  - common to LOC-RIB and Adj-RIB, but not shared across routes
  //  - specific to LOC-RIB or Adj-RIB
  include ietf-bgp-rib-attributes;

  // groupings of annotations for each route or table
  include ietf-bgp-rib-table-attributes;

  organization
    "IETF IDR Working Group";

  contact
    "WG Web:   <http://tools.ietf.org/wg/idr>
     WG List:  <idr@ietf.org>

     Authors: Mahesh Jethanandani (mjethanandani at gmail.com),
              Keyur Patel (keyur at arrcus.com),
              Susan Hares (shares at ndzh.com";

  description
    "Defines a submodule for representing BGP routing table (RIB)
     contents.  The submodule supports 5 logical RIBs per address
     family:

     loc-rib: This is the main BGP routing table for the local routing
     instance, containing best-path selections for each prefix. The
     loc-rib table may contain multiple routes for a given prefix,
     with an attribute to indicate which was selected as the best
     path.  Note that multiple paths may be used or advertised even if
     only one path is marked as best, e.g., when using BGP
     add-paths.  An implementation may choose to mark multiple
     paths in the RIB as best path by setting the flag to true for
     multiple entries.

     adj-rib-in-pre: This is a per-neighbor table containing the NLRI
     updates received from the neighbor before any local input policy
     rules or filters have been applied.  This can be considered the
     'raw' updates from a given neighbor.

     adj-rib-in-post: This is a per-neighbor table containing the
     routes received from the neighbor that are eligible for
     best-path selection after local input policy rules have been
     applied.

     adj-rib-out-pre: This is a per-neighbor table containing routes
     eligible for sending (advertising) to the neighbor before output
     policy rules have been applied.

     adj-rib-out-post: This is a per-neighbor table containing routes
     eligible for sending (advertising) to the neighbor after output
     policy rules have been applied.";

  revision "2019-06-05" {
    description
      "Initial Version";
    reference 
      "RFC XXXX, BGP YANG Model for Service Provider Network.";
  }

  grouping rib {
    description
      "Grouping for rib.";

    container rib {
      config false;

      container attr-sets {
        description
          "Enclosing container for the list of path attribute sets";

        list attr-set {
          key "index";

          description
            "List of path attributes that may be in use by multiple
             routes in the table";

          leaf index {
            type uint64;
            description
              "System generated index for each attribute set.  The
               index is used to reference an attribute set from a
               specific path.  Multiple paths may reference the same
               attribute set.";
          }

          leaf origin {
            type bt:bgp-origin-attr-type;
            description
              "BGP attribute defining the origin of the path
               information.";
          }

          leaf atomic-aggregate {
            type boolean;
            description
              "BGP attribute indicating that the prefix is an atomic
               aggregate, i.e., the peer selected a less specific
               route without selecting a more specific route that is
               included in it.";
          }

          leaf next-hop {
            type inet:ip-address;
            description
              "BGP next hop attribute defining the IP address of the
               router that should be used as the next hop to the
               destination";
          }

          leaf med {
            type uint32;
            description
              "BGP multi-exit discriminator attribute used in BGP route
               selection process";
          }

          leaf local-pref {
            type uint32;
            description
              "BGP local preference attribute sent to internal peers to
               indicate the degree of preference for externally learned
               routes.  The route with the highest local preference
               value is preferred.";
          }

          leaf originator-id {
            type inet:ipv4-address;
            description
              "BGP attribute that provides the id as an IPv4 address
               of the originator of the announcement.";
            reference
              "RFC 4456 - BGP Route Reflection: An Alternative to Full
               Mesh Internal BGP (IBGP)";
          }

          leaf-list cluster-list {
            type inet:ipv4-address;
            description
              "Represents the reflection path that the route has
               passed.";
            reference
              "RFC 4456 - BGP Route Reflection: An Alternative to Full
               Mesh Internal BGP (IBGP)";
          }

          leaf aigp {
            type uint64;
            description
              "BGP path attribute representing the accumulated IGP
               metric for the path";
            reference
              "RFC 7311 - The Accumulated IGP Metric Attribute for BGP";
          }
          container aggregator {
            config false;
            description
              "BGP attribute indicating the prefix has been
               aggregated by the specified AS and router.";

            leaf as {
              type inet:as-number;
              description
                "AS number of the autonomous system that performed the
                 aggregation.";
            }

            leaf as4 {
              type inet:as-number;
              description
                "AS number of the autonomous system that performed the
                 aggregation (4-octet representation).  This value is
                 populated if an upstream router is not 4-octet capable.
                 Its semantics are similar to the AS4_PATH optional
                 transitive attribute";
              reference
                "RFC 6793 - BGP Support for Four-octet AS Number Space";
            }

            leaf address {
              type inet:ipv4-address;
              description
                "IP address of the router that performed the
                 aggregation.";
            }
          }
          container as-path {
            description
              "Enclosing container for the list of AS path segments.

               In the Adj-RIB-In or Adj-RIB-Out, this list should show
               the received or sent AS_PATH, respectively.  For
               example, if the local router is not 4-byte capable, this
               value should consist of 2-octet ASNs or the AS_TRANS
               (AS 23456) values received or sent in route updates.

               In the Loc-RIB, this list should reflect the effective
               AS path for the route, e.g., a 4-octet value if the
               local router is 4-octet capable.";
            reference
              "RFC 4271 - A Border Gateway Protocol 4 (BGP-4)
               RFC 6793 - BGP Support for Four-octet AS Number Space
               RFC 5065 - Autonomous System Confederations for BGP";

            list segment {
              key "type";

              config false;
              uses bgp-as-path-attr;
              description
                "List of AS PATH segments";
            }
          }
          container as4-path {
            description
              "This is the path encoded with 4-octet
               AS numbers in the optional transitive AS4_PATH attribute.
               This value is populated with the received or sent
               attribute in Adj-RIB-In or Adj-RIB-Out, respectively.
               It should not be populated in Loc-RIB since the Loc-RIB
               is expected to store the effective AS-Path in the
               as-path leaf regardless of being 4-octet or 2-octet.";
            reference
              "RFC 6793 - BGP Support for Four-octet AS Number Space";

            list segment {
              key "type";

              config false;
              uses bgp-as-path-attr;
              description
                "List of AS PATH segments";
            }
          }

          container tunnel-encapsulation {
            config false;
            description
              "The Tunnel Encapsulation attribute specifies a set of
               tunnels to a remote destination. The attribute is TLV
               based and allows description of a tunnel type, and the
               relevant information to create the tunnel to the remote
               destination.";

            reference "RFC5512, draft-ietf-idr-tunnel-encaps";

            container tunnels {
              description
                "Surrounding container for the set of tunnels included
                 within the tunnel encapsulation attribute.";

              list tunnel {
                key "type";
                description
                  "List of the tunnels that are specified within the
                   attribute. Keyed on the type of tunnel that the
                   TLV describes.";

                leaf type {
                  type identityref {
                    base "tunnel-encapsulation-type";
                  }
                  description
                    "Type of the tunnel described within the tunnel
                     encapsulation attribute.";
                }
          
                container subtlvs {
                  description
                    "Surrounding container for the list of sub-TLVs
                     within the tunnel encapsulation attribute.";

                  list subtlv {
                    key "type";
                    description
                      "List of the subTLVs that are specified within the
                       TLV instance inside the tunnel encapsulation
                       attribute.";

                    leaf type {
                      type identityref {
                        base "tunnel-encapsulation-subtlv-type";
                      }
                      description
                        "Type of the sub-TLV within the tunnel
                         encapsulation attribute";
                    }

                    leaf-list colors {
                      when "../type = 'tunnel-color'" {
                        description
                          "Only allow list of colors to be specified
                           when the sub-TLV specifies colors
                           associated with the tunnel encapsulation
                           attribute.";
                      }
                      type uint32;
                      description
                        "The colors associated with the tunnel
                         encapsulation attribute, as described by
                         RFC5512.";
                    }

                    container remote-endpoints {
                      when "../type = 'tunnel-remote-endpoint'" {
                        description
                          "Only allow the remote endpoint to be
                           specified when the subTLV is specified to
                           describe remote endpoints.";
                      }

                      description
                        "The remote endpoints associated with the tunnel
                         described by the attribute.";

                      list remote-endpoint {
                        key "endpoint";
                        config false;
                        description
                          "List of the remote endpoints described within
                           the TLV.";

                        leaf as {
                          type inet:as-number;
                          description
                            "The remote AS to which the IP address of
                             the remote endpoint belongs.";
                        }

                        leaf endpoint {
                          type inet:ip-address;
                          description
                            "IP address of the remote endpoint.";
                        }
                      }
                    }
                  }
                }
              }
            }
          }
        }
      }

      container communities {
        description
          "Enclosing container for the list of community attribute
        sets";

        list community {
          key "index";

          config false;
          description
            "List of path attributes that may be in use by multiple
          routes in the table";

          leaf index {
            type uint64;
            description
              "System generated index for each attribute set.  The
              index is used to reference an attribute set from a
              specific path.  Multiple paths may reference the same
              attribute set.";
          }

          uses bgp-community-attr-state;
        }
      }

      container ext-communities {
        description
          "Enclosing container for the list of extended community
           attribute sets";

        list ext-community {
          key "index";

          config false;
          description
            "List of path attributes that may be in use by multiple
             routes in the table";

          leaf index {
            type uint64;
            description
              "System generated index for each attribute set.  The
               index is used to reference an attribute set from a
               specific path.  Multiple paths may reference the same
               attribute set.";
          }

          leaf-list ext-community {
            type rt:route-target;
            description
              "List of BGP extended community attributes. The received
               extended community may be an explicitly modeled
               type or unknown, represented by an 8-octet value
               formatted according to RFC 4360.";
            reference
              "RFC 4360 - BGP Extended Communities Attribute";
          }
        }
      }

      container afi-safis {
	config false;
	description
	  "Enclosing container for address family list";

	list afi-safi {
	  key "afi-safi-name";
	  description
	    "List of afi-safi types.";

	  leaf afi-safi-name {
	    type identityref {
	      base bt:afi-safi-type;
	    }
	    description "AFI,SAFI name.";
	  }

	  container ipv4-unicast {
	    when "../afi-safi-name = 'bt:ipv4-unicast'" {
	      description
		"Include this container for IPv4 unicast RIB";
	    }
	    description
	      "Routing tables for IPv4 unicast -- active when the
             afi-safi name is ipv4-unicast";

	    uses ipv4-loc-rib;
	    uses ipv4-adj-rib;
	  }

	  container ipv6-unicast {
	    when "../afi-safi-name = 'bt:ipv6-unicast'" {
	      description
		"Include this container for IPv6 unicast RIB";
	    }
	    description
	      "Routing tables for IPv6 unicast -- active when the
             afi-safi name is ipv6-unicast";

	    uses ipv6-loc-rib;
	    uses ipv6-adj-rib;
	  }
	}
      }
      description
	"Top level container for BGP RIB";
    }
  }
}
